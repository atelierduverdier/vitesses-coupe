# -*- coding: utf-8 -*-
# =========================================================================
# importer_outil_coupe.FCMacro — un bouton pour l'atelier CAM
# © Atelier du Verdier — licence LGPL-2.1-or-later (cf. LICENSE).
# =========================================================================
# Un clic : on choisit une fraise DANS SA BIBLIOTHÈQUE, et elle arrive dans
# le Job avec son Tool Controller et ses vitesses.
#
# La macro ne CRÉE plus d'outil. Elle partait auparavant d'un fichier JSON
# exporté par l'appli et fabriquait une fraise à partir de lui — mais
# l'appli sait déjà écrire dans la bibliothèque FreeCAD, si bien qu'on se
# retrouvait avec la MÊME fraise deux fois : celle de l'appli, complète, et
# celle de la macro, à la géométrie déduite. Relevé par Christophe le
# 31/08/2026, capture à l'appui : six entrées pour cinq fraises.
#
# Le parcours tient donc en deux gestes :
#   1. dans l'appli : régler la fraise, puis « ↑ Écrire dans FreeCAD… » ;
#   2. ici : ce bouton, qui la pose dans le Job avec ses vitesses.
#
# INSTALLER LE BOUTON (une fois) :
#   1. copier ce fichier et icone_outil_coupe.svg dans le dossier des
#      macros — il est VERSIONNÉ (FreeCAD 1.1 :
#      ~/.local/share/FreeCAD/v1-1/Macro). En cas de doute, la réponse vient
#      de FreeCAD lui-même : FreeCAD.getUserMacroDir(True) ;
#   2. Outils → Personnaliser… → onglet « Macros » : texte du menu
#      « Importer un outil de coupe », icône, puis Ajouter ;
#   3. onglet « Barres d'outils », atelier CAM, y déplacer la commande.
#
# =========================================================================
#  DEUX PIÈGES, MESURÉS SUR FreeCAD 1.1.3
# =========================================================================
# 1. LES UNITÉS. HorizFeed, VertFeed, HorizRapid et VertRapid sont comptées
#    en mm/s quand l'interface affiche des mm/min. `tc.HorizFeed = 6300` ne
#    lève aucune erreur et vaut 378 000 mm/min — soixante fois trop. Seule
#    la chaîne portant son unité est juste : `"6300 mm/min"`.
#
# 2. LES RAPIDES N'APPARTIENNENT PAS À L'OUTIL. Elles vivent dans le
#    SetupSheet du Job, qui les RÉIMPOSE au Tool Controller à chaque
#    recalcul : posées sur le contrôleur, elles retombent à zéro sans le
#    moindre message. C'est juste — un rapide dépend de la machine, pas de
#    la fraise — mais rien ne le dit.
# =========================================================================

import json
from pathlib import Path

import FreeCAD
import FreeCADGui
from PySide import QtGui

TITRE = "Importer un outil de coupe"

# Là où l'appli garde les vitesses. Un fichier d'outil FreeCAD ne peut pas
# les porter : le format a bien un champ libre, mais FreeCAD le VIDE dès
# qu'il réécrit l'outil.
VITESSES = Path.home() / '.config' / 'vitesses-coupe' / 'vitesses-freecad.json'


def _dire(texte, erreur=False):
    boite = QtGui.QMessageBox.critical if erreur else QtGui.QMessageBox.information
    boite(FreeCADGui.getMainWindow(), TITRE, texte)


def _choisir(question, choix):
    valeur, ok = QtGui.QInputDialog.getItem(
        FreeCADGui.getMainWindow(), TITRE, question, choix, 0, False)
    return choix.index(valeur) if ok else None


def _lire_json(chemin):
    try:
        return json.loads(Path(chemin).read_text(encoding='utf-8'))
    except (OSError, ValueError):
        return None


def _vitesse(objet, propriete, valeur_mm_min):
    """Écrit une vitesse EN mm/min sur une propriété comptée en mm/s.

    Le seul endroit de la macro où une vitesse est posée, pour qu'il n'y
    ait qu'un seul endroit où se tromper. Voir le piège 1 en tête.
    """
    try:
        v = float(valeur_mm_min)
    except (TypeError, ValueError):
        return None
    if v <= 0:
        return None
    setattr(objet, propriete, "%f mm/min" % v)
    return getattr(objet, propriete).getValueAs('mm/min')


def _dossier_outils():
    """Le magasin d'outils de CETTE installation de FreeCAD.

    On le demande à FreeCAD plutôt que de le deviner : le dossier de
    données est versionné (v1-1, v1-2, v26-3…) et plusieurs versions
    cohabitent presque toujours.
    """
    base = Path(FreeCAD.getUserAppDataDir()) / 'CamAssets' / 'Tools'
    return base if (base / 'Library').is_dir() else None


def _bibliotheques(dossier):
    listes = []
    for fctl in sorted((dossier / 'Library').glob('*.fctl')):
        d = _lire_json(fctl)
        if d:
            listes.append({'label': d.get('label') or fctl.stem,
                           'outils': d.get('tools') or []})
    return listes


def _jobs(doc):
    return [o for o in doc.Objects
            if hasattr(o, 'Proxy') and hasattr(o, 'Tools') and hasattr(o, 'SetupSheet')]


def main():
    doc = FreeCAD.ActiveDocument
    if doc is None:
        _dire("Aucun document ouvert.", erreur=True)
        return

    jobs = _jobs(doc)
    if not jobs:
        _dire("Ce document ne contient aucun Job.\n\n"
              "Dans l'atelier CAM : Job → créer, puis relancer.", erreur=True)
        return

    dossier = _dossier_outils()
    if dossier is None:
        _dire("Aucune bibliothèque d'outils dans cette installation de FreeCAD.",
              erreur=True)
        return

    # --- 1. Quelle fraise, dans quelle bibliothèque ? ---------------------
    libs = [b for b in _bibliotheques(dossier) if b['outils']]
    if not libs:
        _dire("Aucune bibliothèque d'outils garnie.\n\n"
              "Dans l'appli « Vitesses de coupe » : régler la fraise puis "
              "« ↑ Écrire dans FreeCAD… ».", erreur=True)
        return

    if len(libs) == 1:
        lib = libs[0]
    else:
        i = _choisir("Quelle bibliothèque ?",
                     ["%s  (%d outils)" % (b['label'], len(b['outils'])) for b in libs])
        if i is None:
            return
        lib = libs[i]

    vitesses_connues = _lire_json(VITESSES) or {}
    entrees = []
    for e in lib['outils']:
        chemin = dossier / 'Bit' / str(e.get('path', ''))
        d = _lire_json(chemin)
        if not d:
            continue
        entrees.append({'chemin': chemin, 'nom': d.get('name') or chemin.stem,
                        'nr': e.get('nr'),
                        'vitesses': vitesses_connues.get(chemin.name) or {},
                        'diametre': (d.get('parameter') or {}).get('Diameter', '?')})
    if not entrees:
        _dire("Cette bibliothèque ne contient aucun fichier d'outil lisible.",
              erreur=True)
        return

    etiquettes = []
    for e in entrees:
        v = e['vitesses']
        etiquettes.append(
            "%s  —  %s%s" % (e['nom'], e['diametre'],
                             ("  ·  %s tr/min, %s mm/min" % (v.get('n'), v.get('vf')))
                             if v.get('n') else "  ·  vitesses inconnues"))
    i = _choisir("Quelle fraise poser dans le Job ?", etiquettes)
    if i is None:
        return
    outil = entrees[i]

    job = jobs[0]
    if len(jobs) > 1:
        j = _choisir("Dans quel Job ?", [x.Label for x in jobs])
        if j is None:
            return
        job = jobs[j]

    # --- 2. La poser dans le Job -----------------------------------------
    doc.openTransaction("Importer " + outil['nom'])
    try:
        from Path.Tool.toolbit import ToolBit
        from Path.Tool import Controller as ControleurOutil

        # On lit le fichier DÉJÀ dans la bibliothèque : aucune fraise n'est
        # créée, donc aucun doublon possible.
        fraise = ToolBit.from_file(str(outil['chemin'])).attach_to_doc(doc)
        doc.recompute()

        numeros = [getattr(tc, 'ToolNumber', 0) for tc in job.Tools.Group]
        tc = ControleurOutil.Create("TC: " + outil['nom'], tool=fraise)
        job.Proxy.addToolController(tc)
        tc.ToolNumber = outil['nr'] or ((max(numeros) + 1) if numeros else 1)

        v = outil['vitesses']
        pose = {}
        if v.get('n'):
            tc.SpindleSpeed = float(v['n'])
            pose['Broche'] = "%.0f tr/min" % float(v['n'])
        for propriete, cle, etiquette in (('HorizFeed', 'vf', 'Avance'),
                                          ('VertFeed', 'plunge', 'Plongée')):
            obtenu = _vitesse(tc, propriete, v.get(cle))
            if obtenu is not None:
                pose[etiquette] = "%.0f mm/min" % obtenu
        # Les rapides vont sur le JOB — voir le piège 2 en tête.
        for propriete, cle, etiquette in (('HorizRapid', 'rapidH', 'Rapide horizontal'),
                                          ('VertRapid', 'rapidV', 'Rapide vertical')):
            obtenu = _vitesse(job.SetupSheet, propriete, v.get(cle))
            if obtenu is not None:
                pose[etiquette] = "%.0f mm/min" % obtenu
        doc.commitTransaction()
    except Exception as e:                       # noqa: BLE001
        doc.abortTransaction()
        _dire("Rien n'a été modifié.\n\n%s : %s" % (type(e).__name__, e), erreur=True)
        return

    doc.recompute()
    try:
        FreeCADGui.Selection.clearSelection()
        FreeCADGui.Selection.addSelection(tc)
    except Exception:                            # noqa: BLE001
        pass

    lignes = ["« %s » est dans %s, outil n° %d."
              % (outil['nom'], job.Label, tc.ToolNumber), ""]
    if pose:
        for cle in ('Broche', 'Avance', 'Plongée'):
            if cle in pose:
                lignes.append("   %-18s %s" % (cle, pose[cle]))
        rapides = [c for c in ('Rapide horizontal', 'Rapide vertical') if c in pose]
        if rapides:
            lignes += ["", "Sur le Job (ils valent pour tous les outils) :"]
            for cle in rapides:
                lignes.append("   %-18s %s" % (cle, pose[cle]))
    else:
        lignes += ["Aucune vitesse connue pour cette fraise.", "",
                   "Dans l'appli « Vitesses de coupe » : la régler, puis",
                   "« ↑ Écrire dans FreeCAD… ». Elles seront retenues et",
                   "reviendront ici au prochain passage."]
    _dire("\n".join(lignes))


main()
